--  *****************************************************************
--  DLINKPV2-LLDP-EXT-MIB.mib : LLDP Extension MIB
--
--  Copyright (c) 2014 D-Link Corporation, all rights reserved.
--
--  *****************************************************************
DLINKPV2-LLDP-EXT-MIB DEFINITIONS ::= BEGIN

    IMPORTS
        MODULE-IDENTITY, OBJECT-IDENTITY, OBJECT-TYPE,Integer32
            FROM SNMPv2-SMI
		MODULE-COMPLIANCE, OBJECT-GROUP
		    FROM SNMPv2-CONF			
        TruthValue
		    FROM SNMPv2-TC
        SnmpAdminString
            FROM SNMP-FRAMEWORK-MIB
		dlinkDGS1100CommonV2           
            FROM DGS1100SERMGMT-MIB;	
           
    primeV2LldpExtMIB MODULE-IDENTITY
        LAST-UPDATED "201406030000Z"
        ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for DLINK LLDP private function."
        REVISION "201406030000Z"
        DESCRIPTION
            "This is the first version of the MIB file.
            "
        ::= { dlinkDGS1100CommonV2 8 }

-- -----------------------------------------------------------------------------
    v2LldpExtMIBNotifications    OBJECT IDENTIFIER ::= { primeV2LldpExtMIB 0 }
    v2LldpExtMIBObjects          OBJECT IDENTIFIER ::= { primeV2LldpExtMIB 1 }
    v2LldpExtMIBConformance      OBJECT IDENTIFIER ::= { primeV2LldpExtMIB 2 }
-- -----------------------------------------------------------------------------

    v2LldpExtLldpEnabled OBJECT-TYPE
        SYNTAX          TruthValue
        MAX-ACCESS      read-write
        STATUS          current
        DESCRIPTION
            "This object indicates whether the LLDP feature is
            globally enabled.
            " 
        ::= { v2LldpExtMIBObjects 1 }
		
	v2LldpExtLldpTrapEnabled OBJECT-TYPE
        SYNTAX          TruthValue
        MAX-ACCESS      read-write
        STATUS          current
        DESCRIPTION
            "This object indicates whether the LLDP Trap feature is
            globally enabled.
            " 
        ::= { v2LldpExtMIBObjects 2 }
	

-- -----------------------------------------------------------------------------

    v2LldpExtRemTable OBJECT-TYPE
        SYNTAX      SEQUENCE OF V2LldpExtRemEntry
        MAX-ACCESS  not-accessible
        STATUS      current
        DESCRIPTION
                "This table contains one or more rows per physical network
                connection known to this agent.  The agent may wish to ensure
                that only one V2LldpExtRemEntry is present for each local port,
                or it may choose to maintain multiple lldpRemEntries for
                the same local port."
        ::= { v2LldpExtMIBObjects 3 }

    v2LldpExtRemEntry OBJECT-TYPE
        SYNTAX      V2LldpExtRemEntry
        MAX-ACCESS  not-accessible
        STATUS      current
        DESCRIPTION
                "Information about a particular physical network connection.
                Entries may be created and deleted in this table by the agent,
                if a physical topology discovery process is active."
        INDEX   {
               v2LldpExtRemLocalPortNum,
               v2LldpExtRemIndex
        }
        ::= { v2LldpExtRemTable 1 }

    V2LldpExtRemEntry ::= SEQUENCE {
          v2LldpExtRemLocalPortNum       Integer32,
          v2LldpExtRemIndex              Integer32,
          v2LldpExtRemChassisIdSubtype   INTEGER,
          v2LldpExtRemChassisId          OCTET STRING,
          v2LldpExtRemPortIdSubtype      INTEGER,
          v2LldpExtRemPortId             OCTET STRING,
          v2LldpExtRemPortDesc           SnmpAdminString
    }

    v2LldpExtRemLocalPortNum  OBJECT-TYPE
        SYNTAX      Integer32 (1..4096)
        MAX-ACCESS  not-accessible
        STATUS      current
        DESCRIPTION
                "The index value used to identify the port component
                (contained in the local chassis with the LLDP agent)
                associated with this entry.  The v2LldpExtRemLocalPortNum
                identifies the port on which the remote system information
                is received.

                The value of this object is used as a port index to the
                v2LldpExtRemTable."
        ::= { v2LldpExtRemEntry 1 }

    v2LldpExtRemIndex  OBJECT-TYPE
        SYNTAX      Integer32 (1..2147483647)
        MAX-ACCESS  not-accessible
        STATUS      current
        DESCRIPTION
                "This object represents an arbitrary local integer value used
                by this agent to identify a particular connection instance,
                unique only for the indicated remote system.

                An agent is encouraged to assign monotonically increasing
                index values to new entries, starting with one, after each
                reboot.  It is considered unlikely that the v2LldpExtRemIndex
                will wrap between reboots."
        ::= { v2LldpExtRemEntry 2 }

    v2LldpExtRemChassisIdSubtype  OBJECT-TYPE
        SYNTAX  INTEGER {
                chassisComponent(1),
                interfaceAlias(2),
                portComponent(3),
                macAddress(4),
                networkAddress(5),
                interfaceName(6),
                local(7)
            }

        MAX-ACCESS  read-only
        STATUS      current
        DESCRIPTION
                "The type of encoding used to identify the chassis associated
                with the remote system."
        ::= { v2LldpExtRemEntry 3 }

    v2LldpExtRemChassisId  OBJECT-TYPE
        SYNTAX      OCTET STRING (SIZE (1..255))
        MAX-ACCESS  read-only
        STATUS      current
        DESCRIPTION
                "The string value used to identify the chassis component
                associated with the remote system."
        ::= { v2LldpExtRemEntry 4 }

    v2LldpExtRemPortIdSubtype  OBJECT-TYPE
        SYNTAX  INTEGER {
                interfaceAlias(1),
                portComponent(2),
                macAddress(3),
                networkAddress(4),
                interfaceName(5),
                agentCircuitId(6),
                local(7)
            }
        MAX-ACCESS  read-only
        STATUS      current
        DESCRIPTION
                "The type of port identifier encoding used in the associated
                'v2LldpExtRemPortId' object."
        ::= { v2LldpExtRemEntry 5 }

    v2LldpExtRemPortId  OBJECT-TYPE
        SYNTAX      OCTET STRING (SIZE (1..255))
        MAX-ACCESS  read-only
        STATUS      current
        DESCRIPTION
                "The string value used to identify the port component
                associated with the remote system."
        ::= { v2LldpExtRemEntry 6 }

    v2LldpExtRemPortDesc  OBJECT-TYPE
        SYNTAX      SnmpAdminString (SIZE(0..255))
        MAX-ACCESS  read-only
        STATUS      current
        DESCRIPTION
                "The string value used to identify the description of
                the given port associated with the remote system."
        ::= { v2LldpExtRemEntry 7 }

-- -----------------------------------------------------------------------------
-- MIB Notifications statements
-- -----------------------------------------------------------------------------
    v2LldpExtDatabaseChanged    NOTIFICATION-TYPE
        STATUS        current
        DESCRIPTION
            "This trap is sent when LLDP database changed."
        ::= { v2LldpExtMIBNotifications 1 }

-- ------------------------------------------------------------------------------------
-- MIB Conformance statements
-- ------------------------------------------------------------------------------------
	v2LldpExtMIBCompliances  OBJECT IDENTIFIER    ::= { v2LldpExtMIBConformance 1 }	
	v2LldpExtMIBGroups       OBJECT IDENTIFIER    ::= { v2LldpExtMIBConformance 2 } 	
-- compliance statements

    v2LldpExtMIBCompliance MODULE-COMPLIANCE
        STATUS      current
        DESCRIPTION
            "The compliance statement for entities which
             implement the DLINKPV2-LLDP-EXT-MIB."
        MODULE      -- this module
        MANDATORY-GROUPS       {
            v2LldpExtBasicCfgGroup
        }        
	    ::= { v2LldpExtMIBCompliances 1 }
	
    v2LldpExtBasicCfgGroup OBJECT-GROUP
		OBJECTS   {   
            v2LldpExtLldpEnabled,
			v2LldpExtLldpTrapEnabled
		}
		STATUS      current
		DESCRIPTION 
		    "A collection of objects configures the LLDP feature."
		::= { v2LldpExtMIBGroups 1 }
    
END
