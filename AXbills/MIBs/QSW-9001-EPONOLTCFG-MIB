EPON-OLT-CONFIG-MIB DEFINITIONS ::= BEGIN

IMPORTS
    IpAddress, Unsigned32, Integer32, Counter32, TimeTicks, Gauge32, Counter64,
    MODULE-IDENTITY, OBJECT-IDENTITY, OBJECT-TYPE, enterprises     
      FROM SNMPv2-SMI     
    DateAndTime, MacAddress, TimeStamp, RowStatus, TruthValue, DisplayString, TEXTUAL-CONVENTION
      FROM SNMPv2-TC
    eponOltCfg  FROM  EPON-CONFIG-MIB  ;
      
--------------------------------------------------------------------------------
--  eponOltCfg[OLT属性管理项](1.3.6.1.4.1.27514.1.10.1)
-------------------------------------------------------------------------------- 
eponOltProperty OBJECT-IDENTITY
   STATUS current
   DESCRIPTION
     "OLT property"
   ::= { eponOltCfg 1 }
       
eponOltName     OBJECT-TYPE
   SYNTAX       DisplayString (SIZE(0..32))
   MAX-ACCESS   read-write
   STATUS       current
   DESCRIPTION
     "OLT description"
   ::= { eponOltProperty 1 }
    
eponOltType OBJECT-TYPE
   SYNTAX      DisplayString (SIZE(0..32))
   MAX-ACCESS  read-only
   STATUS      current
   DESCRIPTION
     "OLT device type"
   ::= { eponOltProperty 2 }
   
eponOltDeviceUpTime  OBJECT-TYPE
   SYNTAX        TimeStamp
   MAX-ACCESS    read-only
   STATUS         current
   DESCRIPTION
     "OLT up time"
   ::= { eponOltProperty 3 }

eponOltDeviceStyle OBJECT-TYPE
   SYNTAX      INTEGER
     {
       fixed(1),
       chassisBased(2),
       other(3)
     }
   MAX-ACCESS  read-only
   STATUS      current
   DESCRIPTION
     "
     The device stype of either fixed or chassis based：        
     fixed(1) - such as pizza box
     chassisBased(2) - Have number of slots for installing service card, power card, etc.        
     "
   ::= { eponOltProperty 4 }
      
------BOARD TABLE---------------------------------------------------------------------
eponBoardTable   OBJECT-TYPE
   SYNTAX      SEQUENCE OF EponBoardEntry
   MAX-ACCESS  not-accessible
   STATUS      current
   DESCRIPTION
      "board info table"
   ::= { eponOltCfg 2 }
eponBoardEntry	OBJECT-TYPE
	SYNTAX	 	  EponBoardEntry
	MAX-ACCESS  not-accessible
	STATUS		  current
	DESCRIPTION
		"BoardEntry table"
	INDEX	{ eponBoardIndex }
	::= { eponBoardTable 1 }

EponBoardEntry	::= SEQUENCE {
		eponBoardIndex			  INTEGER,
		eponBoardState			  INTEGER,
		eponBoardConfigType	  INTEGER,
		eponBoardTrueType			INTEGER,
		eponBoardSwVersion    OCTET STRING,
		eponBoardHwVersion		OCTET STRING,
		eponBoardReset			  INTEGER
    }

eponBoardIndex	OBJECT-TYPE
	SYNTAX	 	  INTEGER
	MAX-ACCESS  read-only
	STATUS		  current
	DESCRIPTION
		"slot Index"
	::= { eponBoardEntry 1 }

eponBoardState	OBJECT-TYPE
	SYNTAX	 	  INTEGER
	{
	  down(0),
	  up(1)
	}
	MAX-ACCESS  read-only
	STATUS		  current
	DESCRIPTION
	" down:0   up:1"
	::= { eponBoardEntry 2 }
	
eponBoardConfigType	 OBJECT-TYPE
	SYNTAX	 	    INTEGER
	MAX-ACCESS    read-write
	STATUS		    current
	DESCRIPTION
	"config type
	typedef enum
	{
      BOARD_TYPE_NULL = 0,
      BOARD_TYPE_CONTROL_BCM56334,
      BOARD_TYPE_LINE_2_GE_COMBO_BCM5482S,
      BOARD_TYPE_LINE_2_10GE_FIBER_BCM8727,
      BOARD_TYPE_LINE_4_EPON_CS8022,
      BOARD_TYPE_NUM
	}"
	::= { eponBoardEntry 3 }

eponBoardTrueType	OBJECT-TYPE
	SYNTAX	 	  INTEGER(0..10)
	MAX-ACCESS  read-only
	STATUS		  current
	DESCRIPTION
	"true type
	typedef enum
	{
      BOARD_TYPE_NULL = 0,
      BOARD_TYPE_CONTROL_BCM56334,
      BOARD_TYPE_LINE_2_GE_COMBO_BCM5482S,
      BOARD_TYPE_LINE_2_10GE_FIBER_BCM8727,
      BOARD_TYPE_LINE_4_EPON_CS8022,
      BOARD_TYPE_NUM
	}"
	::= { eponBoardEntry 4 }
	
eponBoardSwVersion	OBJECT-TYPE
	SYNTAX	   	OCTET STRING (SIZE(0..255))
	MAX-ACCESS  read-only
	STATUS		  current
	DESCRIPTION
	"software version"
	::= { eponBoardEntry 5 }	
	
eponBoardHwVersion	OBJECT-TYPE
	SYNTAX	   	OCTET STRING (SIZE(0..255))
	MAX-ACCESS  read-only
	STATUS		  current
	DESCRIPTION
	"hardware version"
	::= { eponBoardEntry 6 }
	
eponBoardReset	OBJECT-TYPE
	SYNTAX	 	  INTEGER(0..1)
	MAX-ACCESS  read-write
	STATUS		  current
	DESCRIPTION
		"reset"
	::= { eponBoardEntry 7 }
	
------GLOBAL ONU MULTICAST TABLE---------------------------------------------------------------------

eponGlobalMulticastProperty   OBJECT-IDENTITY
   STATUS      current
   DESCRIPTION
   "global onu multicast info"
   ::= { eponOltCfg 3 }
   
eponChannelNum	OBJECT-TYPE
	SYNTAX	 	  INTEGER (0..1024)
	MAX-ACCESS  read-write
	STATUS		  current
	DESCRIPTION
		"channel number"
	::= { eponGlobalMulticastProperty 1 }

eponLiveTime	OBJECT-TYPE
	SYNTAX	 	  INTEGER (3..300)
	MAX-ACCESS  read-write
	STATUS		  current
	DESCRIPTION
	"live time without igmp report"
	::= { eponGlobalMulticastProperty 2 }
	
eponPreviewTimes	 OBJECT-TYPE
	SYNTAX	 	    INTEGER (0..10)
	MAX-ACCESS    read-write
	STATUS		    current
	DESCRIPTION
	"preview times"
	::= { eponGlobalMulticastProperty 3 }

eponPreviewInterTime	OBJECT-TYPE
	SYNTAX	 	  INTEGER (180..600)
	MAX-ACCESS  read-write
	STATUS		  current
	DESCRIPTION
	"preview time interval"
	::= { eponGlobalMulticastProperty 4 }
	
eponPreviewOnceTime	OBJECT-TYPE
	SYNTAX	 	  INTEGER (60..300)
	MAX-ACCESS  read-write
	STATUS		  current
	DESCRIPTION
	"software version"
	::= { eponGlobalMulticastProperty 5 }	
	
eponPrevieResetTime	OBJECT-TYPE
	SYNTAX	 	  INTEGER (1800..7200)
	MAX-ACCESS  read-write
	STATUS		  current
	DESCRIPTION
	"hardware version"
	::= { eponGlobalMulticastProperty 6 }
	
--
-- END of EPON-OLT-CONFIG-MIB
--      
END
