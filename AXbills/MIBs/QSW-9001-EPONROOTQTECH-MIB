EPON-CONFIG-MIB DEFINITIONS ::= BEGIN

IMPORTS
    IpAddress, Unsigned32, Integer32, Counter32, TimeTicks, Gauge32, Counter64,
    MODULE-IDENTITY, OBJECT-IDENTITY, OBJECT-TYPE, enterprises     
      FROM SNMPv2-SMI     
    DateAndTime, MacAddress, TimeStamp, RowStatus, TruthValue, DisplayString, TEXTUAL-CONVENTION
      FROM SNMPv2-TC;
      
--------------------------------------------------------------
    greennet MODULE-IDENTITY
        LAST-UPDATED    "200712050000Z"  -- Dec 5, 2000
        ORGANIZATION    "GreenNet Systems, Inc."
        CONTACT-INFO    "GreenNet Systems, Inc.
                         E-mail: support@green-net.com.cn"
        DESCRIPTION     "GREENNET Master MIB OID defines and documentation."
        REVISION        "201510100000Z"  -- Oct 10, 2015
        DESCRIPTION     "Initial MIB creation."
    	::= { enterprises 27514 }
    	
--GREENNET Products----------------------------------------------------
datacom		OBJECT IDENTIFIER ::= { greennet 1 }

--DataCom Products-----------------------------------------------------
eponCfg		OBJECT IDENTIFIER ::= {datacom 13}

--epon funtion---------------------------------------------------------
eponOltCfg			OBJECT IDENTIFIER ::= { eponCfg 1 }
eponPonCfg			OBJECT IDENTIFIER ::= { eponCfg 2 }
eponOnuCfg			OBJECT IDENTIFIER ::= { eponCfg 3 }
eponUniCfg      OBJECT IDENTIFIER ::= { eponCfg 4 }
--eponDeployCfg   OBJECT IDENTIFIER ::= { eponCfg 5 }    ---- 7500 deploy ----
eponAlarmMgmt   OBJECT IDENTIFIER ::= { eponCfg 10 }

--
-- END of EPON-CONFIG-MIB
--

END
