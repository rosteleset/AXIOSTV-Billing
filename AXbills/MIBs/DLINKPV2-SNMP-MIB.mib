--  *****************************************************************
--  DLINKPV2-SNMP-MIB.mib : SNMP management MIB
--
--  Copyright (c) 2014 D-Link Corporation, all rights reserved.
--
--  *****************************************************************
DLINKPV2-SNMP-MIB DEFINITIONS ::= BEGIN

	IMPORTS
   		MODULE-IDENTITY, OBJECT-TYPE, NOTIFICATION-TYPE,
   		Unsigned32, IpAddress
       		FROM SNMPv2-SMI
   		DisplayString, TruthValue
       		FROM SNMPv2-TC
   		MODULE-COMPLIANCE, OBJECT-GROUP, NOTIFICATION-GROUP
       		FROM SNMPv2-CONF               		
        SnmpEngineID, SnmpAdminString, SnmpSecurityModel                      
            FROM SNMP-FRAMEWORK-MIB
        ifIndex, InterfaceIndexOrZero
            FROM IF-MIB                  
   		dlinkDGS1100CommonV2		
            FROM DGS1100SERMGMT-MIB;
       
   
   primeV2SnmpMIB	MODULE-IDENTITY
   		LAST-UPDATED "201406030000Z"
   		ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for configuring SNMP 
            ( Simple Network Management Protocol )"
            
        REVISION "201406030000Z"
        DESCRIPTION
            "This is the first version of the MIB file for 'SNMP'
            functionality."  
       
        ::= { dlinkDGS1100CommonV2 15 } 
            
-- -----------------------------------------------------------------------------
    
	v2SnmpMIBNotifications 	OBJECT IDENTIFIER ::= { primeV2SnmpMIB 0 }
	v2SnmpMIBObjects 		OBJECT IDENTIFIER ::= { primeV2SnmpMIB 1 }
	v2SnmpMIBConformance	OBJECT IDENTIFIER ::= { primeV2SnmpMIB 2 }

-- -------------------------------------------------------------------------- 
	v2SnmpGeneral			OBJECT IDENTIFIER ::= { v2SnmpMIBObjects 1 }
		
	v2SnmpServiceEnabled OBJECT-TYPE
   		SYNTAX          TruthValue
  		MAX-ACCESS      read-write
   		STATUS          current
   		DESCRIPTION
           "A Boolean value represents the SNMP server is Enabled or Disabled."
   		::= { v2SnmpGeneral 1 }
        
-- -------------------------------------------------------------------------- 
	v2SnmpMIBTrap				OBJECT IDENTIFIER ::= { v2SnmpMIBObjects 2 }
	
	v2SnmpTrapGlobalEnabled OBJECT-TYPE
       	SYNTAX          TruthValue
  		MAX-ACCESS      read-write
   		STATUS          current
   		DESCRIPTION
            "A Boolean value to represent the global state of sending of trap
            packets.
            "
   		::= { v2SnmpMIBTrap 1 }

    v2SnmpTrapGlobalNotifyEnable OBJECT-TYPE
        SYNTAX          BITS {         
            linkUp(0),
            linkDown(1),
            coldStart(2),
            warmStart(3),
            authentication(4)
        }
        MAX-ACCESS  read-write
        STATUS      current
        DESCRIPTION
            "This object indicates global state about whether a specified
            notification is enabled or not.
            If a bit corresponding to a notification is set to 1, then 
            the specified notification can be generated.

            linkUp(0)    - sending a standard linkUp notification (defined in IF-MIB). 
            linkDown(1)  - sending a standard linkDown notification (defined in IF-MIB).  
            coldStart(2) - sending a standard coldStart notification (defined in SNMPv2-MIB).
            warmStart(3) - sending a standard warmStart notification (defined in SNMPv2-MIB).
            Note: please use snmpEnableAuthenTraps (defined in SNMPv2-MIB) to control 
            the generation of authenticationFailure traps.
            "
        ::= { v2SnmpMIBTrap 2 }
      
-- -------------------------------------------------------------------------- 	 
    v2SnmpAccessCfg 			OBJECT IDENTIFIER ::= { v2SnmpMIBObjects 3 }
         
    v2SnmpCommunityTable  OBJECT-TYPE
        SYNTAX          SEQUENCE OF V2SnmpCommunityEntry
        MAX-ACCESS      not-accessible
        STATUS          current
        DESCRIPTION
            "This table consists of a list of communities.
            "       
        ::= { v2SnmpAccessCfg 1 }

    v2SnmpCommunityEntry  OBJECT-TYPE
        SYNTAX          V2SnmpCommunityEntry
        MAX-ACCESS      not-accessible
        STATUS          current
        DESCRIPTION
            "An entry defines additional information which is not covered at
            snmpCommunityTable (defined in SNMP-COMMUNITY-MIB).
            An entry appears in this table when a community is created in 
            snmpCommunityTable.
            "
        INDEX     { v2SnmpCommunityName }
        ::= { v2SnmpCommunityTable 1 }

    V2SnmpCommunityEntry ::= SEQUENCE {
        v2SnmpCommunityName               SnmpAdminString,
        v2SnmpCommunityAccessListName     DisplayString       
    }

    v2SnmpCommunityName  OBJECT-TYPE
        SYNTAX          SnmpAdminString
        MAX-ACCESS      not-accessible
        STATUS          current
        DESCRIPTION
           "This object indicates the name of the community."
        ::= { v2SnmpCommunityEntry 1 }
   	
    v2SnmpCommunityAccessListName  OBJECT-TYPE
        SYNTAX          DisplayString 
        MAX-ACCESS      read-write
        STATUS          current
        DESCRIPTION
           "This object indicates the name of a standard access list to control
           the user to use this community string to access to the SNMP agent. 
           Specify the valid user in the source address field of the access 
           list entry.
           A zero length string indicates the access list is not specified.          
           "
        ::= { v2SnmpCommunityEntry 2 }

-- --------------------------------------------------------------------------
    v2SnmpHostTable  OBJECT-TYPE
        SYNTAX          SEQUENCE OF V2SnmpHostEntry
        MAX-ACCESS      not-accessible
        STATUS          current
        DESCRIPTION
            "This table consists of a list of recipients for the SNMP
            notification. 
            "       
        ::= { v2SnmpAccessCfg 2 }

    v2SnmpHostEntry  OBJECT-TYPE
        SYNTAX          V2SnmpHostEntry
        MAX-ACCESS      not-accessible
        STATUS          current
        DESCRIPTION
            "An entry consists of additional informaiton which is not covered
            at snmpTargetAddrTable and snmpTargetParamsTable (defined in 
            SNMP-TARGET-MIB).           
            An entry appears in this table when a target address is created in 
            snmpTargetAddrTable.
            "            
        INDEX     { v2SnmpHostIndex }
        ::= { v2SnmpHostTable 1 }

    V2SnmpHostEntry ::= SEQUENCE {
        v2SnmpHostIndex         Unsigned32,
        v2SnmpHostIPv4Addr      IpAddress,
        v2SnmpHostSecurity      INTEGER,
        v2SnmpHostCommunityName SnmpAdminString       
    }
     
	v2SnmpHostIndex     OBJECT-TYPE
		SYNTAX          Unsigned32
		MAX-ACCESS      not-accessible
		STATUS  current
		DESCRIPTION
		      "The ID number for this entry."
		::= { v2SnmpHostEntry 1 }		

    v2SnmpHostIPv4Addr  OBJECT-TYPE
        SYNTAX          IpAddress
        MAX-ACCESS      read-write
        STATUS          current
        DESCRIPTION
           "This object indicates the IPv4 address of the recipients."
        ::= { v2SnmpHostEntry 2 }

    v2SnmpHostSecurity  OBJECT-TYPE
        SYNTAX  INTEGER {
            v1(1),
            v2c(2)
        }
        MAX-ACCESS      read-write
        STATUS          current
        DESCRIPTION
           "This object indicates the User-based Security Model for the recipients."
        ::= { v2SnmpHostEntry 3 }

    v2SnmpHostCommunityName OBJECT-TYPE
        SYNTAX              SnmpAdminString (SIZE(1..16))
        MAX-ACCESS          read-write
        STATUS              current
        DESCRIPTION
           "This object indicates the address name of the recipients."
        ::= { v2SnmpHostEntry 4 }

--  ***************************************************************************	
--  Conformance
--  ***************************************************************************			   		
	v2SnmpCompliances OBJECT IDENTIFIER ::= { v2SnmpMIBConformance 1 }
		
-- units of conformance		
	v2SnmpGroups OBJECT IDENTIFIER ::= { v2SnmpMIBConformance 2 }
		
	v2SnmpSysCfgGroup OBJECT-GROUP
		OBJECTS { 
		    v2SnmpServiceEnabled	    
		}
		STATUS current
		DESCRIPTION 
			"A collection of objects provides the information for SNMP server."
		::= { v2SnmpGroups 1 }
		
	v2SnmpTrapCfgGroup OBJECT-GROUP
		OBJECTS { 
		    v2SnmpTrapGlobalEnabled,
		    v2SnmpTrapGlobalNotifyEnable    
		}
		STATUS current
		DESCRIPTION 
			"A collection of objects provides system-wide control of traps."
			::= { v2SnmpGroups 2 }
	
	v2SnmpCommunityExtGroup OBJECT-GROUP
        OBJECTS         { 
            v2SnmpCommunityAccessListName
        }
        STATUS          current
        DESCRIPTION
            "The collection of objects provides configuration for community feature
            which extends SNMP community. 
            "
            ::= { v2SnmpGroups 3 }
    			

END
