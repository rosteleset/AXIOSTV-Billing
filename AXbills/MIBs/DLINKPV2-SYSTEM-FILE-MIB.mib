-- *****************************************************************
-- DLINKPV2-SYSTEM-FILE-MIB: D-Link System File MIB
--
--  Copyright (c) 2014 D-Link Corporation, all rights reserved.
--
-- *****************************************************************


DLINKPV2-SYSTEM-FILE-MIB DEFINITIONS ::= BEGIN

    IMPORTS
        MODULE-IDENTITY, OBJECT-TYPE, Unsigned32, IpAddress
            FROM SNMPv2-SMI
        MODULE-COMPLIANCE, OBJECT-GROUP
            FROM SNMPv2-CONF
        TEXTUAL-CONVENTION, TruthValue, RowStatus, DisplayString
		    FROM SNMPv2-TC
        dlinkDGS1100CommonV2
            FROM DGS1100SERMGMT-MIB;

    primeV2SystemFileMIB MODULE-IDENTITY
        LAST-UPDATED    "201405260000Z"
        ORGANIZATION    "D-Link Corp."
        CONTACT-INFO
            "   D-Link Corporation

                Postal: No. 289, Sinhu 3rd Rd., Neihu District,
                        Taipei City 114, Taiwan, R.O.C
                Tel:     +886-2-66000123
                E-mail: tsd@dlink.com.tw
            "
        DESCRIPTION
            "This MIB module defines objects for managing system critical files
            (e.g configuration and firmware.)
            "
        REVISION        "201405260000Z"
        DESCRIPTION
            "This is the first version of the MIB file."

        ::= { dlinkDGS1100CommonV2 22 }

--
-- Node definitions
--

    v2sfMIBNotifications OBJECT IDENTIFIER ::= { primeV2SystemFileMIB 0 }
    v2sfMIBObjects       OBJECT IDENTIFIER ::= { primeV2SystemFileMIB 1 }
    v2sfMIBConformance	 OBJECT IDENTIFIER ::= { primeV2SystemFileMIB 2 }

-- -----------------------------------------------------------------------------
    v2sfBootInfoObjects		OBJECT IDENTIFIER ::= { v2sfMIBObjects 1 }

    v2sfCheckingBootImageCheck OBJECT-TYPE
        SYNTAX          TruthValue
        MAX-ACCESS      read-write
        STATUS          current
        DESCRIPTION
            "This object indicates whether displays the information of the
            specified next boot image to let user understand whether the
            specified file is suitable to be a boot image or not, which some
            information should be displayed such as purpose of the file,
            version number, time stamp, and checksum etc.
            "
        ::= { v2sfBootInfoObjects 1 }

    v2sfBootImageCheckResult OBJECT-TYPE
        SYNTAX          DisplayString
        MAX-ACCESS      read-only
        STATUS          current
        DESCRIPTION
            "This object indicates the information of the specified next boot
            image such as the purpose of the file, version number, time stamp,
            and checksum etc.
            "
        ::= { v2sfBootInfoObjects 2 }

-- -----------------------------------------------------------------------------
    v2sfBootImageTable OBJECT-TYPE
        SYNTAX          SEQUENCE OF V2sfBootImageEntry
        MAX-ACCESS      not-accessible
        STATUS          current
        DESCRIPTION
            "The table is used to display information for boot images of units."
        ::= { v2sfBootInfoObjects 3 }

	v2sfBootImageEntry OBJECT-TYPE
        SYNTAX          V2sfBootImageEntry
        MAX-ACCESS      not-accessible
        STATUS          current
        DESCRIPTION
            "An entry contains version information of a system."
        INDEX   {
            v2sfBootImageIndex
        }
        ::= { v2sfBootImageTable 1 }

    V2sfBootImageEntry ::= SEQUENCE {
		v2sfBootImageIndex   	 Unsigned32,
        v2sfBootImageInWorking   TruthValue
    }

	v2sfBootImageIndex OBJECT-TYPE
        SYNTAX          Unsigned32 (1..65535)
        MAX-ACCESS      not-accessible
        STATUS          current
        DESCRIPTION
             "This object indicates the index of boot image."
        ::= { v2sfBootImageEntry 1 }

    v2sfBootImageInWorking OBJECT-TYPE
        SYNTAX          TruthValue
        MAX-ACCESS      read-only
        STATUS          current
        DESCRIPTION
            "This object indicates whether the entry is the current boot image."
        ::= { v2sfBootImageEntry 2 }

-- -----------------------------------------------------------------------------
    v2sfCopyTable OBJECT-TYPE
       SYNTAX           SEQUENCE OF V2sfCopyEntry
       MAX-ACCESS       not-accessible
       STATUS           current
       DESCRIPTION
           "A table contains the information for file copy. There will at any
           time be either 0 or 1 row in this table, and the only valid index
           for this table is 1.  It is only a table so that we may take
           advantage of the RowStatus textual convention for configuring
           the copying parameters."
       ::= { v2sfMIBObjects 2 }

    v2sfCopyEntry OBJECT-TYPE
       SYNTAX           V2sfCopyEntry
       MAX-ACCESS       not-accessible
       STATUS           current
       DESCRIPTION
           "An entry contains parameters for copy."
       INDEX  { v2sfCopyIndex }
       ::= { v2sfCopyTable 1 }

    V2sfCopyEntry ::= SEQUENCE {
        v2sfCopyIndex                Unsigned32,
        v2sfCopyType                 INTEGER,
        v2sfCopySrcUrl               OCTET STRING,
        v2sfCopyDstUrl               OCTET STRING,
        v2sfCopyRemoteAddr           IpAddress,
        v2sfCopyErrorStatus          DisplayString,
        v2sfCopyRowStatus            RowStatus
        }

    v2sfCopyIndex OBJECT-TYPE
        SYNTAX          Unsigned32 (1)
        MAX-ACCESS      not-accessible
        STATUS          current
        DESCRIPTION
            "This object uniquely identifies this row.
            The only legal value for this object is 1."
        ::= { v2sfCopyEntry 1 }

    v2sfCopyType OBJECT-TYPE
        SYNTAX          INTEGER {
            localToTftpRemote(1),
            tftpRemoteToLocal(2)
        }
        MAX-ACCESS      read-create
        STATUS          current
        DESCRIPTION
            "This object indicates the type of the copy.
            'localToTftpRemote' - Upload file remote host via TFTP.
            'tftpRemoteToLocal' - Download file from remote host via TFTP.
            "
       ::= { v2sfCopyEntry 2 }

    v2sfCopySrcUrl OBJECT-TYPE
        SYNTAX      OCTET STRING (SIZE (0..799))
        MAX-ACCESS  read-create
        STATUS      current
        DESCRIPTION
            "This object indicates the source URL for the source file to be copied.
            The special form 'image1' and 'image2' 
            are reserved to indicate the system files.
            "
        ::= { v2sfCopyEntry 3 }

    v2sfCopyDstUrl OBJECT-TYPE
        SYNTAX      OCTET STRING (SIZE (0..799))
        MAX-ACCESS  read-create
        STATUS      current
        DESCRIPTION
            "This object indicates the destination URL for the copied file.
            The special form 'image1', and 'image2' are reserved to 
            indicate the system files.
            "
        ::= { v2sfCopyEntry 4 }

    v2sfCopyRemoteAddr OBJECT-TYPE
        SYNTAX             IpAddress
        MAX-ACCESS         read-create
        STATUS             current
        DESCRIPTION
           "This object indicates the address of the remote host.
           "
        ::= { v2sfCopyEntry 5 }

    v2sfCopyErrorStatus  OBJECT-TYPE
        SYNTAX          DisplayString
        MAX-ACCESS      read-only
        STATUS          current
        DESCRIPTION
            "Status of file copy."
        ::= { v2sfCopyEntry 6 }

    v2sfCopyRowStatus OBJECT-TYPE
        SYNTAX          RowStatus
        MAX-ACCESS      read-create
        STATUS          current
        DESCRIPTION
            "The status of this conceptual row.
            The writable columns in a row cannot be changed if the row is
            'active'."
        ::= { v2sfCopyEntry 7 }

-- -----------------------------------------------------------------------------
    v2sfCfgReplaceTable OBJECT-TYPE
       SYNTAX           SEQUENCE OF V2sfCfgReplaceEntry
       MAX-ACCESS       not-accessible
       STATUS           current
       DESCRIPTION
           "A table contains the information for replacing the current running
           configuration file. There will at any time be either 0 or 1 row
           in this table, and the only valid index for this table is 1."
       ::= { v2sfMIBObjects 3 }

    v2sfCfgReplaceEntry OBJECT-TYPE
       SYNTAX           V2sfCfgReplaceEntry
       MAX-ACCESS       not-accessible
       STATUS           current
       DESCRIPTION
           "An entry contains parameters for configure replace."
       INDEX  { v2sfCfgReplaceIndex }
       ::= { v2sfCfgReplaceTable 1 }

    V2sfCfgReplaceEntry ::= SEQUENCE {
        v2sfCfgReplaceIndex               Unsigned32,
        v2sfCfgReplaceSrcType             INTEGER,
        v2sfCfgReplaceSrcUrl              OCTET STRING,
        v2sfCfgReplaceRemoteAddr          IpAddress,
        v2sfCfgReplaceActionType          INTEGER,
        v2sfCfgReplaceErrorStatus         DisplayString,
        v2sfCfgReplaceRowStatus           RowStatus
        }

    v2sfCfgReplaceIndex OBJECT-TYPE
        SYNTAX          Unsigned32 (1)
        MAX-ACCESS      not-accessible
        STATUS          current
        DESCRIPTION
            "This object uniquely identifies this row.
            The only legal value for this object is 1."
        ::= { v2sfCfgReplaceEntry 1 }

    v2sfCfgReplaceSrcType OBJECT-TYPE
        SYNTAX          INTEGER {
            tftpRemote(1)
        }
        MAX-ACCESS      read-only
        STATUS          current
        DESCRIPTION
            "This object indicates where to get the file to replace the current
            running configuration.

            'tftpRemote' - Get the replacing configuration file from remote host via TFTP.
            "
       ::= { v2sfCfgReplaceEntry 2 }

    v2sfCfgReplaceSrcUrl OBJECT-TYPE
        SYNTAX      OCTET STRING (SIZE (0..799))
        MAX-ACCESS  read-create
        STATUS      current
        DESCRIPTION
            "This object indicates the source URL for the source configuration file
            to be executed."
        ::= { v2sfCfgReplaceEntry 3 }

    v2sfCfgReplaceRemoteAddr OBJECT-TYPE
        SYNTAX             IpAddress
        MAX-ACCESS         read-create
        STATUS             current
        DESCRIPTION
           "This object indicates the address of the remote host.
           "
        ::= { v2sfCfgReplaceEntry 4 }
		
    v2sfCfgReplaceActionType OBJECT-TYPE
        SYNTAX          INTEGER {
            effectiveImmediately(1),
            effectiveNextBoot(2)
        }
        MAX-ACCESS      read-create
        STATUS          current
        DESCRIPTION
            "This object indicates the type of action to import the configuration file.
             0 means take effect after restart,1 means take effect immediately."
        ::= { v2sfCfgReplaceEntry 5 }
	   
    v2sfCfgReplaceErrorStatus  OBJECT-TYPE
        SYNTAX          DisplayString
        MAX-ACCESS      read-only
        STATUS       current
        DESCRIPTION
            "This object indicates the processing status about the replacement of
            current running configuration.
            "
        ::= { v2sfCfgReplaceEntry 6 }

    v2sfCfgReplaceRowStatus OBJECT-TYPE
        SYNTAX          RowStatus
        MAX-ACCESS      read-create
        STATUS          current
        DESCRIPTION
            "The status of this conceptual row.
            The writable columns in a row cannot be changed if the row is
            'active'."
        ::= { v2sfCfgReplaceEntry 7 }

-- -----------------------------------------------------------------------------
    v2sfClearRunCfg OBJECT-TYPE
        SYNTAX      INTEGER   {
            clear_cfg_ip_reboot(1),
            clear_cfg_no_ip_reboot(2),
            clear_cfg_no_reboot(3),
            noOp(4)
        }
        MAX-ACCESS  read-write
        STATUS      current
        DESCRIPTION
            "When set to 'clear_cfg_ip_reboot', this object is used to clear 
            running-config including IP address and save to flash then reboot.
            When set to 'clear_cfg_no_ip_reboot', this object is used to clear 
            running-config except IP address  and save to flash then reboot.
            When set to 'clear_cfg_no_reboot', this object is used to clear
            running-config including IP address and save to flash but no reboot.
            No action is taken if this object is set to 'noOp'.
            When read, the value 'noOp' is returned."
        ::= { v2sfMIBObjects 4 }
		
-- -----------------------------------------------------------------------------
	v2sfNextBootUp OBJECT-TYPE
        SYNTAX      OCTET STRING (SIZE (0..799))
        MAX-ACCESS  read-create
        STATUS      current
        DESCRIPTION
            "This object indicates the destination URL for next boot up.
            The special form 'image1', and 'image2' are reserved to 
            indicate the system files.
            "
        ::= { v2sfMIBObjects 5 }
		
-- -----------------------------------------------------------------------------
    v2sfResetSystem OBJECT-TYPE
        SYNTAX      INTEGER   {
            reset(1),
            noOp(2)
        }
        MAX-ACCESS  read-write
        STATUS      current
        DESCRIPTION
            "This object is used to reset system when set to 'reset'.
            It will clear system configuration, save and reboot the system.
            No action is taken if this object is set to 'noOp'.
            When read, the value 'noOp' is returned."
        ::= { v2sfMIBObjects 6 }

-- -----------------------------------------------------------------------------
    v2sfSaveRunCfg	OBJECT-TYPE
        SYNTAX      INTEGER   {
            save(1),
            noOp(2)
        }
        MAX-ACCESS  read-write
        STATUS      current
        DESCRIPTION
            "When set to 'save', this object is used to save running-config.
            No action is taken if this object is set to 'noOp'.
            When read, the value 'noOp' is returned."
        ::= { v2sfMIBObjects 7 }

-- -----------------------------------------------------------------------------
    v2sfRebootSystem OBJECT-TYPE
        SYNTAX      INTEGER   {
            reboot(1),
            noOp(2)
        }
        MAX-ACCESS  read-write
        STATUS      current
        DESCRIPTION
            "This object is used to reboot system when set to 'reboot'.
            No action is taken if this object is set to 'noOp'.
            When read, the value 'noOp' is returned."
        ::= { v2sfMIBObjects 8 }

-- -----------------------------------------------------------------------------
    v2sfCompliances   OBJECT IDENTIFIER ::= { v2sfMIBConformance 1 }

    v2sfCompliance MODULE-COMPLIANCE
        STATUS      current
        DESCRIPTION
            "The compliance statement for entities which implement the
            DLINKPV2-SYSTEM-FILE-MIB."
        MODULE
            MANDATORY-GROUPS {
                v2sfBootInfoGroup,
                v2sfCopyGroup,
                v2sfCfgReplaceGroup,
                v2sfClearCfgGroup
            }
        OBJECT  v2sfCopyType
            DESCRIPTION
                "It is compliant to support only a subset of
                values: 'localToTftpRemote', and
                'tftpRemoteToLocal'."

        OBJECT  v2sfCfgReplaceSrcType
            DESCRIPTION
                "It is compliant to support only a subset of
                values: 'tftpRemote'."

        ::= { v2sfCompliances 1 }

    v2sfGroups   OBJECT IDENTIFIER ::= { v2sfMIBConformance 2 }

    v2sfBootInfoGroup OBJECT-GROUP
        OBJECTS {
            v2sfCheckingBootImageCheck,
            v2sfBootImageCheckResult,
            v2sfBootImageInWorking
        }
        STATUS      current
        DESCRIPTION
            "A collection of objects providing information about the boot configuration
            and boot image."
        ::= { v2sfGroups 1 }

    v2sfCopyGroup OBJECT-GROUP
        OBJECTS {
            v2sfCopyType,
            v2sfCopySrcUrl,
            v2sfCopyDstUrl,
            v2sfCopyRemoteAddr,
            v2sfCopyErrorStatus,
            v2sfCopyRowStatus
        }
        STATUS      current
        DESCRIPTION
            "A collection of objects providing information for the parameters
            of the copy function."
        ::= { v2sfGroups 2 }

    v2fCfgReplaceGroup OBJECT-GROUP
        OBJECTS {
            v2sfCfgReplaceSrcType,
            v2sfCfgReplaceSrcUrl,
            v2sfCfgReplaceRemoteAddr,
	    v2sfCfgReplaceActionType,
            v2sfCfgReplaceErrorStatus,
            v2sfCfgReplaceRowStatus
        }
        STATUS      current
        DESCRIPTION
            "A collection of objects providing information for the parameters
            of the configure replace function."
        ::= { v2sfGroups 3 }

    v2sfClearCfgGroup OBJECT-GROUP
        OBJECTS {
            v2sfClearRunCfg,
            v2sfResetSystem
        }
        STATUS      current
        DESCRIPTION
            "An object providing the clear function."
        ::= { v2sfGroups 4 }

END
