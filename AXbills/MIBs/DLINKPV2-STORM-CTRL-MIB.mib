--  *****************************************************************
--  DLINKPV2-STORM-CTRL-MIB.mib : Storm Control MIB
--
--  Copyright (c) 2014 D-Link Corporation, all rights reserved.
--
--  *****************************************************************
DLINKPV2-STORM-CTRL-MIB DEFINITIONS ::= BEGIN

    IMPORTS
           MODULE-IDENTITY, OBJECT-TYPE, NOTIFICATION-TYPE,
           Integer32
               FROM SNMPv2-SMI           
           MODULE-COMPLIANCE, OBJECT-GROUP, NOTIFICATION-GROUP
               FROM SNMPv2-CONF        
           ifIndex, InterfaceIndex
               FROM IF-MIB
           Unsigned32
                FROM SNMPv2-SMI
           dlinkDGS1100CommonV2        
                FROM DGS1100SERMGMT-MIB;
   
   primeV2StormCtrlMIB    MODULE-IDENTITY
           LAST-UPDATED "201404260000Z"
           ORGANIZATION "D-Link Corp."
        CONTACT-INFO
            "        D-Link Corporation

             Postal: No. 289, Sinhu 3rd Rd., Neihu District,
                     Taipei City 114, Taiwan, R.O.C
             Tel:     +886-2-66000123
             E-mail: tsd@dlink.com.tw
            "
        DESCRIPTION
            "This MIB module defines objects for Storm Control"
            
        REVISION "201404260000Z"
        DESCRIPTION
            "This is the first version of the MIB file for 'Storm Control'
            functionality."
        ::= { dlinkDGS1100CommonV2 17 } 

    V2StormCtlTrafficType ::= TEXTUAL-CONVENTION
        STATUS          current
        DESCRIPTION
            "The type of storm control traffic type.
            broadcast(1) - broadcast storm.
            multicast(2) - including unknown L2 multicast, known L2 
                           multicast, unknown IP multicast and known 
                           IP multicast.
            unicast(3)   - when the action is configured as 'shutdown mode', 
                           unicast refers to both known and unknown 
                           unicast packet; Otherwise, unicast refers to 
                           unknown unicast packet. "
        SYNTAX  INTEGER {
            none(1),
            broadcast(2),
            multicast(3),
            unicast(4)
        }   
            
    V2StormCtlThrTypeValue ::= TEXTUAL-CONVENTION
        STATUS          current
        DESCRIPTION
        "Denotes a generic threshold value.

         A V2StormCtlThrTypeValue value is always interpreted within the context
         of a V2StormCtlThrType value.  Every usage of the V2StormCtlThrTypeValue
         textual convention is required to specify the V2StormCtlThrType
         object that provides the context.  
         "
         SYNTAX  INTEGER  {
             noLimit(1),
             limit_16Kbps(2),
             limit_32Kbps(3),
             limit_64Kbps(4),
             limit_128Kbps(5),
             limit_256Kbps(6),
             limit_512Kbps(7),
             limit_1Mbps(8),
             limit_2Mbps(9),
             limit_4Mbps(10),
             limit_8Mbps(11),
             limit_16Mbps(12),
             limit_32Mbps(13),
             limit_64Mbps(14),
             limit_128Mbps(15),
             limit_256Mbps(16),
             limit_512Mbps(17)
         }
         
-- 
--	MIB OBJECTS     
--      
    v2StormCtrlMIBObjects        OBJECT IDENTIFIER ::= { primeV2StormCtrlMIB 1 }
    v2StormCtrlMIBConformance    OBJECT IDENTIFIER ::= { primeV2StormCtrlMIB 2 }
                            
-- --------------------------------------------------------------------------
    v2StormCtrlTrafficInfoTable OBJECT-TYPE
        SYNTAX          SEQUENCE OF V2StormCtrlTrafficInfoEntry
        MAX-ACCESS      not-accessible
        STATUS          current
        DESCRIPTION
            "A table consists of a list of status information for traffic types
            on interfaces. Only the interface/traffic-type on which the storm
            control is enabled will present on this table.
            "
        ::= { v2StormCtrlMIBObjects 1 }

    v2StormCtrlTrafficInfoEntry OBJECT-TYPE
        SYNTAX          V2StormCtrlTrafficInfoEntry
        MAX-ACCESS      not-accessible
        STATUS          current
        DESCRIPTION
            "An entry presents the status of a traffic type on an interface."
        INDEX    { 
            ifIndex
        }
        ::= { v2StormCtrlTrafficInfoTable 1 }

    V2StormCtrlTrafficInfoEntry ::= SEQUENCE {                                                 
        v2StormCtrlCurTrafficType       	V2StormCtlTrafficType,
        v2StormCtrlCurTrafficValue          V2StormCtlThrTypeValue
    }
    
    v2StormCtrlCurTrafficType OBJECT-TYPE
		    SYNTAX          V2StormCtlTrafficType
		    MAX-ACCESS      read-write
		    STATUS          current
		    DESCRIPTION
		        "This object indicates the traffic type of the entry."
        ::= { v2StormCtrlTrafficInfoEntry 1 }                  
    
    v2StormCtrlCurTrafficValue OBJECT-TYPE
        SYNTAX          V2StormCtlThrTypeValue
        MAX-ACCESS      read-write
        STATUS          current
        DESCRIPTION
            "Indicating the current traffic value on the interface."
        ::= { v2StormCtrlTrafficInfoEntry 2 }
          
--  ***************************************************************************    
--  Conformance
--  ***************************************************************************                       
    v2StormCtrlCompliances OBJECT IDENTIFIER ::= { v2StormCtrlMIBConformance 1 }
        
    v2StormCtrlCompliance MODULE-COMPLIANCE
        STATUS current
        DESCRIPTION 
            "The compliance statement for entities which implement the 
            DLINKPV2-STORM-CTRL-MIB."
        MODULE -- this module
        MANDATORY-GROUPS { v2StormCtrlBaiscGroup }
        ::= { v2StormCtrlCompliances 1 }
        
    v2StormCtrlGroup OBJECT IDENTIFIER ::= { v2StormCtrlMIBConformance 2 }
        
    v2StormCtrlBaiscGroup OBJECT-GROUP
        OBJECTS { 
            v2StormCtrlCurTrafficType,
            v2StormCtrlCurTrafficValue
        }
        STATUS current
        DESCRIPTION 
            "A collection of objects providing the information for storm control"
        ::= { v2StormCtrlGroup 1 }
   
                            
END
