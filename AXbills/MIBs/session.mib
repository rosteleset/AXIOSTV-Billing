-- Do not edit this file.
-- It is generated automatically by mib-expand
-- from session.mib.in and *.mibdef.
--			Ascend Session Mib
--
--			Ascend Communications, Inc
--			1275 Harbor Bay Pkwy
--			Alameda, CA 94502
--			+1 510 769 6001
--			info@ascend.com
--
--		Copyright (c) 1993-1998 Ascend Communications, Inc.
--		All rights reserved.
--
-- $Id: session.mib,v 1.2 2007/11/15 09:29:39 axbills Exp $
-- This file is generated automatically for TAOS version 8.0.5.
--
-- 11 Mar 97 rm  Initially created
-- 29 Mar 99 mk  Added ssnActiveIdleTime to the sessionActiveTable.
-- 29 Oct 99 goli Description of ssnActiveIdleTime modified.

ASCEND-SESSION-MIB DEFINITIONS ::= BEGIN

    IMPORTS
	sessionStatusGroup
	    FROM ASCEND-MIB
	IpAddress, TimeTicks
	    FROM RFC1155-SMI
	OBJECT-TYPE
	    FROM RFC-1212;

    DisplayString	::=	OCTET STRING

	--
	-- Ascend Session Status Group
	--
	-- This group contains a table of the status for each
	-- possible session in the system.
	--

    ssnStatusMaximumSessions OBJECT-TYPE
	SYNTAX		INTEGER
	ACCESS		read-only
	STATUS		mandatory
	DESCRIPTION	"The maximum number of sessions that can exist
			 in the system."
	::= { sessionStatusGroup 1 }

    sessionStatusTable	OBJECT-TYPE
	SYNTAX		SEQUENCE OF SessionStatusEntry
	ACCESS		not-accessible
	STATUS		mandatory
	DESCRIPTION	"A list of session status entries."
	::= { sessionStatusGroup 2 }

    sessionStatusEntry	OBJECT-TYPE
	SYNTAX		SessionStatusEntry
	ACCESS		not-accessible
	STATUS		mandatory
	DESCRIPTION	"An entry containing object variables to describe
			 a session."
	INDEX		{ ssnStatusIndex }
	::= { sessionStatusTable 1 }

    SessionStatusEntry ::=
	SEQUENCE {
	    ssnStatusIndex
		INTEGER,
	    ssnStatusValidFlag
		INTEGER,
	    ssnStatusUserName
		DisplayString,
	    ssnStatusUserIPAddress
		IpAddress,
	    ssnStatusUserSubnetMask
		IpAddress,
	    ssnStatusCurrentService
		INTEGER,
	    ssnStatusCallReferenceNum
		INTEGER
	}

    ssnStatusIndex	OBJECT-TYPE
	SYNTAX		INTEGER
	ACCESS		read-only
	STATUS		mandatory
	DESCRIPTION	"The index number for this session status entry. Its
			 value ranges from 1 to 'ssnStatusMaximumSessions'."
	::= { sessionStatusEntry 1 }

    ssnStatusValidFlag  OBJECT-TYPE
	SYNTAX		INTEGER {
			    invalid(1),
			    valid(2)
			}
	ACCESS		read-write
	STATUS		mandatory
	DESCRIPTION	"Value indicates whether this entry contains valid
			 information or not. Setting a valid(2) session to invalid(1)
                         causes an effective session termination."
	::= { sessionStatusEntry 2 }

    ssnStatusUserName   OBJECT-TYPE
	SYNTAX		DisplayString
	ACCESS		read-only
	STATUS		mandatory
	DESCRIPTION	"The name of the remote user.  The null string is
			 returned if entry is invalid. For a Radius DNIS 
			 authenticated session, value of User-Name provided in 
			 Radius reply will be used if no second tier 
			 authentication is involved."
	::= { sessionStatusEntry 3 }

    ssnStatusUserIPAddress	OBJECT-TYPE
	SYNTAX		IpAddress
	ACCESS		read-only
	STATUS		mandatory
	DESCRIPTION	"The IP address of the remote user. The value
			 0.0.0.0 is returned if entry is invalid."
	::= { sessionStatusEntry 4 }

    ssnStatusUserSubnetMask	 OBJECT-TYPE
	SYNTAX		IpAddress
	ACCESS		read-only
	STATUS		mandatory
	DESCRIPTION	"The subnet mask of the remote user. The value
			 0.0.0.0 is returned if entry is invalid."
	::= { sessionStatusEntry 5 }

    ssnStatusCurrentService	 OBJECT-TYPE
	SYNTAX		INTEGER {
			    none(1), -- not applicable
			    other(2), -- none of the following
			    ppp(3), -- Point-To-Point Protocol
			    slip(4), -- Serial Line IP
			    mpp(5), -- Multichannel PPP
			    x25(6), -- X.25
			    combinet(7), -- Combinet
			    frameRelay(8), -- Frame Relay
			    euraw(9), -- EUNET Raw HDLC Encapsulation
			    euui(10), -- EUNET UI HDLC Encapsulation
			    telnet(11), -- telnet
			    telnetBinary(12), -- binary telnet
			    rawTcp(13), -- raw TCP
			    terminalServer(14), -- terminal server
			    mp(15), -- Multilink PPP
			    virtualConnect(16), -- Virtual connect to a mode
			    dchannelX25(17), -- X.25 using the D Channel
			    dtpt(18), -- psuedo-tunneling PPP
			    ipFax(19), -- IP-Fax connection
			    atm(20), -- ATM connection
			    hdlcNrm(21), -- HDCL-NRM (SDLC) connection
			    voip(22), -- Voice-over-IP connection
			    visa2(23), -- Visa-II connection
			    netToNet(25) -- Net To Net Service ..
			}
	ACCESS		read-only
	STATUS		mandatory
	DESCRIPTION	"The current service provided to the remote user.
			 The value none(1) is returned if entry is invalid
			 OR if user dials into the terminal server and is
			 in midst of a login sequence."
	::= { sessionStatusEntry 6 }


    ssnStatusCallReferenceNum  OBJECT-TYPE
--	SYNTAX		INTEGER (1..'7fffffff'h)
	SYNTAX		INTEGER
	ACCESS		read-only
	STATUS		mandatory
	DESCRIPTION	"A unique number identifying this session. The value
			 0 is returned if entry is invalid."
	::= { sessionStatusEntry 7 }


    sessionActiveTable  OBJECT-TYPE
	SYNTAX		SEQUENCE OF SessionActiveEntry
	ACCESS		not-accessible
	STATUS		mandatory
	DESCRIPTION	"A list of active session entries.
                         This table is similar to sessionStatusTable with invalid
                         entries screened out and indexed by ssnActiveCallReferenceNum.
                         ssnActiveCallReferenceNum tracks ssnStatusCallReferenceNum of
                         sessionStatusTable."
	::= { sessionStatusGroup 3 }

    sessionActiveEntry	OBJECT-TYPE
	SYNTAX		SessionActiveEntry
	ACCESS		not-accessible
	STATUS		mandatory
	DESCRIPTION	"An entry containing object variables to describe
			 an active session."
	INDEX		{ ssnActiveCallReferenceNum }
	::= { sessionActiveTable 1 }

    SessionActiveEntry ::=
	SEQUENCE {
	    ssnActiveCallReferenceNum
		INTEGER,
	    ssnActiveIndex
		INTEGER,
	    ssnActiveValidFlag
		INTEGER,
	    ssnActiveUserName
		DisplayString,
	    ssnActiveUserIPAddress
		IpAddress,
	    ssnActiveUserSubnetMask
		IpAddress,
	    ssnActiveCurrentService
		INTEGER,
	    ssnActiveIdleTime
		TimeTicks
	}

    ssnActiveCallReferenceNum  OBJECT-TYPE
--	SYNTAX		INTEGER (1..'7fffffff'h)
	SYNTAX		INTEGER
	ACCESS		read-only
	STATUS		mandatory
	DESCRIPTION	"A unique number identifying this active session.
                         Refer to ssnStatusCallReferenceNum for more information."
	::= { sessionActiveEntry 1 }

    ssnActiveIndex	OBJECT-TYPE
	SYNTAX		INTEGER
	ACCESS		read-only
	STATUS		mandatory
	DESCRIPTION	"The index number for this session status entry. Its
			 value ranges from 1 to 'ssnStatusMaximumSessions'.
                         Refer to ssnStatusIndex for more information."
	::= { sessionActiveEntry 2 }

    ssnActiveValidFlag  OBJECT-TYPE
	SYNTAX		INTEGER {
			    invalid(1),
			    valid(2)
			}
	ACCESS		read-write
	STATUS		mandatory
	DESCRIPTION	"All entries will be valid(2).
                         Refer to ssnStatusValidFlag for more information.
                         Setting a vaild(2) session as invalid(1) causes
                         an effective session termination."
	::= { sessionActiveEntry 3 }

    ssnActiveUserName   OBJECT-TYPE
	SYNTAX		DisplayString
	ACCESS		read-only
	STATUS		mandatory
	DESCRIPTION	"The name of the remote user.
                         Refer to ssnStatusUserName for more information.
			 For a Radius DNIS authenticated session, 
			 value of User-Name provided in Radius reply will 
			 be used if no second tier authentication is involved."
	::= { sessionActiveEntry 4 }

    ssnActiveUserIPAddress	OBJECT-TYPE
	SYNTAX		IpAddress
	ACCESS		read-only
	STATUS		mandatory
	DESCRIPTION	"The IP address of the remote user.
                         Refer to ssnStatusUserIPAddress for more information."
	::= { sessionActiveEntry 5 }

    ssnActiveUserSubnetMask	 OBJECT-TYPE
	SYNTAX		IpAddress
	ACCESS		read-only
	STATUS		mandatory
	DESCRIPTION	"The subnet mask of the remote user.
                         Refer to ssnStatusUserSubnetMask for more information."
	::= { sessionActiveEntry 6 }

    ssnActiveCurrentService	 OBJECT-TYPE
	SYNTAX		INTEGER {
			    none(1), -- not applicable
			    other(2), -- none of the following
			    ppp(3), -- Point-To-Point Protocol
			    slip(4), -- Serial Line IP
			    mpp(5), -- Multichannel PPP
			    x25(6), -- X.25
			    combinet(7), -- Combinet
			    frameRelay(8), -- Frame Relay
			    euraw(9), -- EUNET Raw HDLC Encapsulation
			    euui(10), -- EUNET UI HDLC Encapsulation
			    telnet(11), -- telnet
			    telnetBinary(12), -- binary telnet
			    rawTcp(13), -- raw TCP
			    terminalServer(14), -- terminal server
			    mp(15), -- Multilink PPP
			    virtualConnect(16), -- Virtual connect to a mode
			    dchannelX25(17), -- X.25 using the D Channel
			    dtpt(18), -- psuedo-tunneling PPP
			    ipFax(19), -- IP-Fax connection
			    atm(20), -- ATM connection
			    hdlcNrm(21), -- HDCL-NRM (SDLC) connection
			    voip(22), -- Voice-over-IP connection
			    visa2(23), -- Visa-II connection
			    netToNet(25) -- Net To Net Service ..
			}
	ACCESS		read-only
	STATUS		mandatory
	DESCRIPTION	"The current service provided to the remote user.
			 The value none(1) is returned if entry is invalid
			 OR if user dials into the terminal server and is
			 in midst of a login sequence.
                         Refer to ssnStatusCurrentService for more information."
	::= { sessionActiveEntry 7 }

    ssnActiveIdleTime	OBJECT-TYPE
	SYNTAX		TimeTicks
	ACCESS		read-only
	STATUS		mandatory
	DESCRIPTION	"The time current session has been idle.
			 Valid only for sessions terminated on any of the host
                         cards(i.e. dial up sessions), for others 0 is always
                         reported. For non-TNT and non-Max platforms
			 0 is always reported."
	::= { sessionActiveEntry 8 }


    mppActiveStatsTable	OBJECT-TYPE
	SYNTAX		SEQUENCE OF MppActiveStatsEntry
	ACCESS		not-accessible
	STATUS		mandatory
	DESCRIPTION	"A list of active MPP session statistics with invalid
                         entries screened out and indexed by mppStatsMpID."
	::= { sessionStatusGroup 4 }

    mppActiveStatsEntry	OBJECT-TYPE
	SYNTAX		MppActiveStatsEntry
	ACCESS		not-accessible
	STATUS		mandatory
	DESCRIPTION	"An entry containing object variables to describe
			 an active MPP session. The variables are those seen
                         in the Dyn Stat area of the LCD display."
	INDEX		{ mppStatsMpID }
	::= { mppActiveStatsTable 1 }

    MppActiveStatsEntry ::=
	SEQUENCE {
	    mppStatsMpID
		INTEGER,
            mppStatsRemoteName
                DisplayString,
	    mppStatsQuality
		INTEGER,
	    mppStatsBandwidth
		INTEGER,
	    mppStatsTotalChannels
		INTEGER,
	    mppStatsCLU
		INTEGER,
	    mppStatsALU
		INTEGER,
	    mppStatsStartingTimeStamp
		INTEGER
	}

    mppStatsMpID	OBJECT-TYPE
	SYNTAX          INTEGER
	ACCESS          read-only
	STATUS          mandatory
	DESCRIPTION     "The MpID number for this active MPP session entry."
	::= { mppActiveStatsEntry 1 }

    mppStatsRemoteName   OBJECT-TYPE
        SYNTAX          DisplayString
        ACCESS          read-only
        STATUS          mandatory
        DESCRIPTION     "The name of the remote user."
        ::= { mppActiveStatsEntry 2 }

    mppStatsQuality	 OBJECT-TYPE
	SYNTAX		INTEGER {
				good(1),
				fair(2),
				marginal(3),
				poor(4),
				na(5)
			}
	ACCESS		read-only
	STATUS		mandatory
	DESCRIPTION	"Line quality. N/A: No MPP sessions currenly active,
			 Good: <%1 CRC errors,
			 Fair: <%5 CRC errors,
			 Marginal: <%10 CRC errors,
			 Poor: %10 or > CRC errors"
	::= { mppActiveStatsEntry 3 }

    mppStatsBandwidth  OBJECT-TYPE
	SYNTAX		INTEGER
	ACCESS		read-only
	STATUS		mandatory
	DESCRIPTION	"Total bit rate (Kbps) for the MPP session."
	::= { mppActiveStatsEntry 4 }

    mppStatsTotalChannels   OBJECT-TYPE
	SYNTAX		INTEGER
	ACCESS		read-only
	STATUS		mandatory
	DESCRIPTION	"The total number of channels associated with
			 this MPP session."
	::= { mppActiveStatsEntry 5 }

    mppStatsCLU	 OBJECT-TYPE
	SYNTAX		INTEGER
	ACCESS		read-only
	STATUS		mandatory
	DESCRIPTION	"Current percentage of line utilization
			 for transmitted packets during this MPP session."
	::= { mppActiveStatsEntry 6 }

    mppStatsALU	OBJECT-TYPE
	SYNTAX		INTEGER
	ACCESS		read-only
	STATUS		mandatory
	DESCRIPTION	"Average percentage of line utilization
			 for transmitted packets during this MPP session."
	::= { mppActiveStatsEntry 7 }

    mppStatsStartingTimeStamp	 OBJECT-TYPE
	SYNTAX		INTEGER
	ACCESS		read-only
	STATUS		mandatory
	DESCRIPTION	"The starting time for this MPP session in seconds
			 since startup."
	::= { mppActiveStatsEntry 8 }

END
