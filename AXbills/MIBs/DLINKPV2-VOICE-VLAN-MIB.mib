--  *****************************************************************
--  DLINKPV2-VOICE-VLAN-MIB.mib : Voice VLAN MIB
--
--  Copyright (c) 2014 D-Link Corporation, all rights reserved.
--
--  *****************************************************************
DLINKPV2-VOICE-VLAN-MIB DEFINITIONS ::= BEGIN

    IMPORTS
        MODULE-IDENTITY,OBJECT-TYPE,Unsigned32
            FROM SNMPv2-SMI
        MODULE-COMPLIANCE, OBJECT-GROUP
            FROM SNMPv2-CONF
        MacAddress, TruthValue, RowStatus, DateAndTime
            FROM SNMPv2-TC
        PortList, VlanIdOrNone
            FROM Q-BRIDGE-MIB
        InterfaceIndex
            FROM IF-MIB
        SnmpAdminString
            FROM SNMP-FRAMEWORK-MIB
        dlinkDGS1100CommonV2
            FROM DGS1100SERMGMT-MIB;


    primeV2VoiceVlanMIB MODULE-IDENTITY
        LAST-UPDATED "201404260000Z"
        ORGANIZATION "D-Link Corp."
            CONTACT-INFO
                "        D-Link Corporation

                 Postal: No. 289, Sinhu 3rd Rd., Neihu District,
                         Taipei City 114, Taiwan, R.O.C
                 Tel:     +886-2-66000123
                 E-mail: tsd@dlink.com.tw
                "
        DESCRIPTION
            "The MIB module for managing voice VLAN feature."
        REVISION        "201404260000Z"
        DESCRIPTION
            "Initial version of this MIB module."
        ::= { dlinkDGS1100CommonV2 27}

-- -----------------------------------------------------------------------------
-- Node definitions
-- -----------------------------------------------------------------------------

    v2VoiceVlanMIBNotifications  OBJECT IDENTIFIER ::= { primeV2VoiceVlanMIB 0 }
    v2VoiceVlanMIBObjects        OBJECT IDENTIFIER ::= { primeV2VoiceVlanMIB 1 }
    v2VoiceVlanMIBConformance    OBJECT IDENTIFIER ::= { primeV2VoiceVlanMIB 2 }

-- -----------------------------------------------------------------------------
-- v2VoiceVlanGlobal
-- -----------------------------------------------------------------------------
    v2VoiceVlanGlobal    OBJECT IDENTIFIER ::= { v2VoiceVlanMIBObjects 1 }

	v2VoiceVlanEnabled OBJECT-TYPE
        SYNTAX          TruthValue
        MAX-ACCESS      read-write
        STATUS          current
        DESCRIPTION
            "This object enables or disables voice VLAN feature."
        ::= { v2VoiceVlanGlobal 1 }
	
    v2VoiceVlanVlanId OBJECT-TYPE
        SYNTAX          VlanIdOrNone
        MAX-ACCESS      read-write
        STATUS          current
        DESCRIPTION
            "The object specifies the voice VLAN on a switch.
            A value of zero indicates that no voice VLAN has been
            configured.
            It is required to configure the global v2VoiceVlanVlanId and enable
            v2VoiceVlanEnabled to start the voice VLAN function."
        DEFVAL          { 0 }
        ::= { v2VoiceVlanGlobal 2 }

    v2VoiceVlanQos OBJECT-TYPE
        SYNTAX          Unsigned32 (0..7)
        MAX-ACCESS      read-write
        STATUS          current
        DESCRIPTION
            "The priority for the voice VLAN, which is used to distinguish
            the QoS of the voice traffic from data traffic."
        DEFVAL          { 5 }
        ::= { v2VoiceVlanGlobal 3 }

    v2VoiceVlanAgingTime OBJECT-TYPE
        SYNTAX          Unsigned32 (1..65535)
        UNITS           "minutes"
        MAX-ACCESS      read-write
        STATUS          current
        DESCRIPTION
            "The aging time for the voice VLAN, for aging out the voice
            device and the voice VLAN automatically learned member ports."
        DEFVAL          { 720 }
        ::= { v2VoiceVlanGlobal 4 }

    v2VoiceVlanOuiTable OBJECT-TYPE
        SYNTAX          SEQUENCE OF V2VoiceVlanOuiEntry
        MAX-ACCESS      not-accessible
        STATUS current
        DESCRIPTION
            "This table contains the voice VLAN OUI configuration."
        ::= { v2VoiceVlanGlobal 5 }

    v2VoiceVlanOuiEntry OBJECT-TYPE
        SYNTAX          V2VoiceVlanOuiEntry
        MAX-ACCESS      not-accessible
        STATUS          current
        DESCRIPTION
            "An entry indicates an OUI information, which is used to classify
            voice traffic into the voice VLAN. If the source MAC addresses of
            the received packet matches any of the OUI pattern, the received
            packet is determined as voice packet. "
        INDEX { v2VoiceVlanOuiAddr, v2VoiceVlanOuiMask }
        ::= { v2VoiceVlanOuiTable 1 }

    V2VoiceVlanOuiEntry ::=
        SEQUENCE {
            v2VoiceVlanOuiAddr       MacAddress,
            v2VoiceVlanOuiMask       MacAddress,
            v2VoiceVlanOuiDes        SnmpAdminString,
            v2VoiceVlanOuiRowStatus  RowStatus
        }

    v2VoiceVlanOuiAddr OBJECT-TYPE
        SYNTAX          MacAddress
        MAX-ACCESS      not-accessible
        STATUS          current
        DESCRIPTION
            "The MAC address of the OUI referring to this v2VoiceVlanOuiEntry."
        ::= { v2VoiceVlanOuiEntry 1 }

    v2VoiceVlanOuiMask OBJECT-TYPE
        SYNTAX          MacAddress
        MAX-ACCESS      not-accessible
        STATUS          current
        DESCRIPTION
            "Indicates the OUI MAC address matching bitmask."
        ::= { v2VoiceVlanOuiEntry 2 }

    v2VoiceVlanOuiDes OBJECT-TYPE
        SYNTAX          SnmpAdminString (SIZE (0..32))
        MAX-ACCESS      read-create
        STATUS          current
        DESCRIPTION
            "The description of the OUI. A zero length string of this object indicates
            there is no description for this OUI."
        ::= { v2VoiceVlanOuiEntry 3 }

    v2VoiceVlanOuiRowStatus  OBJECT-TYPE
        SYNTAX          RowStatus
        MAX-ACCESS      read-create
        STATUS          current
        DESCRIPTION
            "This object indicates the status of this entry."
        ::= { v2VoiceVlanOuiEntry 4 }
-- -----------------------------------------------------------------------------
    v2VoiceVlanInterface OBJECT IDENTIFIER ::= { v2VoiceVlanMIBObjects 2 }

    v2VoiceVlanInterfaceTable OBJECT-TYPE
        SYNTAX          SEQUENCE OF V2VoiceVlanInterfaceEntry
        MAX-ACCESS      not-accessible
        STATUS          current
        DESCRIPTION
            "This table contains the interface-specific voice VLAN parameters."
        ::= { v2VoiceVlanInterface 1 }

    v2VoiceVlanInterfaceEntry OBJECT-TYPE
        SYNTAX          V2VoiceVlanInterfaceEntry
        MAX-ACCESS      not-accessible
        STATUS          current
        DESCRIPTION
            "An entry indicates the voice VLAN parameters for a port/port-channel."
        INDEX { v2VoiceVlanIfIndex }
        ::= { v2VoiceVlanInterfaceTable 1 }

    V2VoiceVlanInterfaceEntry ::=
        SEQUENCE {
            v2VoiceVlanIfIndex       InterfaceIndex,
            v2VoiceVlanIfEnabled     TruthValue,
            v2VoiceVlanIfMode        INTEGER
        }

    v2VoiceVlanIfIndex OBJECT-TYPE
        SYNTAX          InterfaceIndex
        MAX-ACCESS      not-accessible
        STATUS          current
        DESCRIPTION
            "Indicates the ifIndex of the physical port/port-channel interface."
        ::= { v2VoiceVlanInterfaceEntry 1 }

    v2VoiceVlanIfEnabled OBJECT-TYPE
        SYNTAX          TruthValue
        MAX-ACCESS      read-write
        STATUS          current
        DESCRIPTION
            "Indicates whether the voice VLAN is enabled at the port."
        ::= { v2VoiceVlanInterfaceEntry 2 }

    v2VoiceVlanIfMode OBJECT-TYPE
        SYNTAX          INTEGER {
            autoUntagged(1),
            autoTagged(2),
            manual(3)
        }
        MAX-ACCESS      read-write
        STATUS          current
        DESCRIPTION
            "If auto learning is enabled, the port will be automatically learned
            as voice VLAN member.
            When the port is working in auto tagged mode, and the port captures
            a voice device through the device's OUI, it will join the voice VLAN
            as a tagged member automatically. When the voice device sends tagged
            packets, the switch will change its priority. When the voice device
            sends untagged packets, it will forward them in port's PVID VLAN.
            When the port is working in auto untagged mode, and the port captures
            a voice device through the device's OUI, it will join the voice VLAN
            as an untagged member automatically. When the voice device sends tagged
            packets, the switch will change its priority. When the voice device
            sends untagged packets, it will forward them in voice VLAN." 
        ::= { v2VoiceVlanInterfaceEntry 3 }
-- -----------------------------------------------------------------------------
    v2VoiceVlanInfo      OBJECT IDENTIFIER ::= { v2VoiceVlanMIBObjects 3 }

    v2VoiceVlanMemberPorts OBJECT-TYPE
        SYNTAX      PortList
        MAX-ACCESS  read-only
        STATUS      current
        DESCRIPTION
            "The voice VLAN's member ports, includes the dynamically
            learned ports."
        ::= { v2VoiceVlanInfo 1 }

    v2VoiceVlanDynamicMemberPorts OBJECT-TYPE
        SYNTAX      PortList
        MAX-ACCESS  read-only
        STATUS      current
        DESCRIPTION
            "The voice VLAN's dynamically learned member ports."
        ::= { v2VoiceVlanInfo 2 }

    v2VoiceVlanDeviceTable OBJECT-TYPE
        SYNTAX          SEQUENCE OF V2VoiceVlanDeviceEntry
        MAX-ACCESS      not-accessible
        STATUS          current
        DESCRIPTION
            "This table contains the information about the learned voice devices."
        ::= { v2VoiceVlanInfo 3 }

    v2VoiceVlanDeviceEntry OBJECT-TYPE
        SYNTAX          V2VoiceVlanDeviceEntry
        MAX-ACCESS      not-accessible
        STATUS          current
        DESCRIPTION
            "Indicates the information of the connected voice device."
        INDEX {
            v2VoiceVlanDevicePortIfindex,
            v2VoiceVlanDeviceAddr }
        ::= { v2VoiceVlanDeviceTable 1 }

    V2VoiceVlanDeviceEntry ::=
        SEQUENCE {
            v2VoiceVlanDevicePortIfindex     InterfaceIndex,
            v2VoiceVlanDeviceAddr            MacAddress,
            v2VoiceVlanDeviceStartTime       DateAndTime,
            v2VoiceVlanDeviceStatus          INTEGER
        }

    v2VoiceVlanDevicePortIfindex OBJECT-TYPE
        SYNTAX          InterfaceIndex
        MAX-ACCESS      not-accessible
        STATUS          current
        DESCRIPTION
            "Indicates the ifIndex of the port to which the voice device connects."
        ::= { v2VoiceVlanDeviceEntry 1 }

    v2VoiceVlanDeviceAddr OBJECT-TYPE
        SYNTAX          MacAddress
        MAX-ACCESS      not-accessible
        STATUS          current
        DESCRIPTION
            "Indicates the MAC address of the voice device."
        ::= { v2VoiceVlanDeviceEntry 2 }

     v2VoiceVlanDeviceStartTime OBJECT-TYPE
        SYNTAX          DateAndTime
        MAX-ACCESS      read-only
        STATUS          current
        DESCRIPTION
            "Indicates the start time of the connected voice device,such as 2018-07-29,13:30:15.0."
        ::= { v2VoiceVlanDeviceEntry 3 }

    v2VoiceVlanDeviceStatus OBJECT-TYPE
        SYNTAX          INTEGER {
            active(1),
            aging(2)
        }
        MAX-ACCESS      read-only
        STATUS          current
        DESCRIPTION
            "Indicates the status of the connected voice device."
        ::= { v2VoiceVlanDeviceEntry 4 }

-- -----------------------------------------------------------------------------
-- MIB Conformance statements
-- -----------------------------------------------------------------------------
    v2VoiceVlanMIBCompliances  OBJECT IDENTIFIER
        ::= { v2VoiceVlanMIBConformance 1 }

    v2VoiceVlanMIBGroups  OBJECT IDENTIFIER
        ::= { v2VoiceVlanMIBConformance 2 }

    v2VoiceVlanMIBCompliance MODULE-COMPLIANCE
        STATUS          current
        DESCRIPTION
            "The compliance statement for entities which implement the
            DLINKPV2-VOICE-VLAN-MIB."
        MODULE          -- this module
        MANDATORY-GROUPS  {   v2VoiceVlanBasicGroup  }

        GROUP v2VoiceVlanOUICfgGroup
        DESCRIPTION
            "This group is required for entities that implement classifying
            voice traffic based on OUI patterns."

        GROUP v2VoiceVlanDeviceInfoGroup
        DESCRIPTION
            "This group is required for entities that display voice vlan
            device infomation."

        ::= { v2VoiceVlanMIBCompliances 1 }
          
    v2VoiceVlanBasicGroup OBJECT-GROUP
        OBJECTS {
		    v2VoiceVlanEnabled,
            v2VoiceVlanVlanId,
            v2VoiceVlanQos,
            v2VoiceVlanAgingTime,                       
            v2VoiceVlanMemberPorts,
            v2VoiceVlanDynamicMemberPorts}
        STATUS current
        DESCRIPTION
            "A collection of objects to configure or display the status
            of voice VLAN feature."
        ::= { v2VoiceVlanMIBGroups 1 }

    v2VoiceVlanOUICfgGroup OBJECT-GROUP
        OBJECTS {
            v2VoiceVlanOuiDes,
            v2VoiceVlanOuiRowStatus }
        STATUS current
        DESCRIPTION
            "A collection of objects to configure voice device OUI(s)."
        ::= { v2VoiceVlanMIBGroups 2 }
     
    v2VoiceVlanDeviceInfoGroup OBJECT-GROUP
        OBJECTS {
            v2VoiceVlanDeviceStartTime,
            v2VoiceVlanDeviceStatus
        }
        STATUS current
        DESCRIPTION
            "A collection of objects to display voice device(s)."
        ::= { v2VoiceVlanMIBGroups 3 }
    
 
END
